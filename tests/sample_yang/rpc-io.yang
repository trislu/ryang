module rpc-io {
  yang-version 1.1;
  namespace "urn:test:rpc-io";
  prefix r;

  container sys {
    list item {
      key name;
      leaf name { type string; }
      // action with NO explicit `input` block (only `output`) — its `input`
      // must still exist as an (implicit) schema node that augments can target.
      action reset {
        description "Reset an item.";
        output {
          leaf ok { type boolean; }
        }
      }
    }
  }

  rpc op {
    description "An RPC with neither input nor output declared.";
  }
}
