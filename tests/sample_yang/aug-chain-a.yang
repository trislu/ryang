module aug-chain-a {
  yang-version 1.1;
  namespace "urn:test:aug-chain-a";
  prefix a;

  import aug-chain-b { prefix b; }

  augment "/b:root" {
    container extra {
      leaf e { type string; }
    }
  }
}
